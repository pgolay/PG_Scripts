Function AlignPlaneToPLane( aPlane, aTarg)
	
	'reassigns a plane's axes so that the + axes are
	'most like the target plane
	
	Dim aVec(5), aWVec(2)
	
	aWVec(0) = aTarg(1)
	aWVec(1) = aTarg(1)
	aWVec(2) = aTarg(1)

	aVec(0) = aPlane(1)
	aVec(1) = aPlane(2)
	aVec(2) = aPLane(3)
	aVec(3) = Rhino.VectorReverse(aPlane(1))
	aVec(4) = Rhino.VectorReverse(aPlane(2))
	aVec(5) = Rhino.VectorReverse(aPlane(3))
	
	Dim i, ang, temp, idx, vecX, VecY, VecZ
	
	For i = 0 To 5
		If i = 0 Then
			
			Ang = VectorAngle(aVec(i),aWVec(0))
			idx = 0
		
		Else
			Temp = VectorAngle(aVec(i),aWVec(0))
			If temp<Ang Then 
				ang = Temp
				idx = i
			
			End If
		
		End If
		
	Next
	VecX = aVec(idx)

	
	For i = 0 To 5
		If i = 0 Then
			
			Ang = VectorAngle(aVec(i),aWVec(1))
			idx = 0
		
		Else
			Temp = VectorAngle(aVec(i),aWVec(1))
			If temp<Ang Then 
				ang = Temp
				idx = i
			
			End If
		
		End If
		
	Next
	VecY = aVec(idx)
	
	For i = 0 To 5
		If i = 0 Then
			
			Ang = VectorAngle(aVec(i),aWVec(2))
			idx = 0
		
		Else
			Temp = VectorAngle(aVec(i),aWVec(2))
			Rhino.Print temp
			If temp < Ang Then 
				ang = Temp
				idx = i
			
			End If
		
		End If
		
	Next
	VecZ = aVec(idx)
	
	Dim tempPlane : tempPlane = array(aPLane(0), vecX,VecY,VecZ)
	AlignPlaneToWorld = tempPlane
	
End Function
