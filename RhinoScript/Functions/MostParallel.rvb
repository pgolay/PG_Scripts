Function MostParallel(vec,avec)
	
	Dim i, n, idx, ang, tempAng
	idx = 0
	i = 0
	ang = VectorAngle(Vec, aVec(0))
	
	For i =1 to UBound(aVec)
		
		tempang = VectorAngle(Vec, aVec(i))
		If tempAng > ang then
			ang = tempang
			idx = i
		end if
	Next
	
	MostParallel = idx
	
End Function

'Finds which of an array of vectors is
'most parallel to a test vector
Function VectorAngle(vec1, vec2)
	'find the angle between two vectors
	Dim test1, test2
	
	test1 = Rhino.VectorUnitize(Vec1)
	test2 = Rhino.VectorUnitize(Vec2)

	Dim DblDot : dblDot = Rhino.VectorDotProduct(Test1, Test2)

	Dim dblAngle : dblAngle = Rhino.aCos(dblDot)
	
	If round(dblDot,5) = 1.00000 Then
		dblAngle = 0
	
	End If

	If dblAngle = 0 Then 
		'msgbox "Zero"
		VectorAngle = 0
		Exit Function
	Else 
		'Msgbox n
		VectorAngle = Rhino.ToDegrees(dblAngle)
		
	End If
	
End Function
