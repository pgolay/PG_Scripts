'\\\\\\\\\\\\\\\\\\\\\\\\\
'/////////////////////////

Function IsUpperBound(ByRef arr)

  IsUpperBound = False

  If IsArray(arr) Then

    On Error Resume Next

    UBound arr

    If Err.Number = 0 Then IsUpperBound = True

  End If

End Function
