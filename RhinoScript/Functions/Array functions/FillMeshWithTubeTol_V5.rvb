Option Explicit
'Script written by Pascal

'Script version Wednesday, March 11, 2009

Rhino.AddStartUpScript Rhino.LastLoadedScriptFile
Rhino.AddAlias "FillMeshWithTubeTol", "_NoEcho _-RunScript (FillMeshWithTubetol)"

Private OldCSamp,OldAngTol' OldLSamp

'If isEmpty(oldLSamp) Then
'	OldLSamp = 32
'End If

If isEmpty(oldCSamp) Then
	OldCSamp = 32
End If

If isEmpty(oldAngTol) Then
	oldAngTol = 5
End If

Call FillMeshWithTubeTol()
Sub FillMeshWithTubeTol()
	
	Dim sMesh: sMesh = Rhino.GetObject("Select mesh", 32, True)
	If IsNull(sMesh) Then Exit Sub
		
	Dim sCrv: sCrv = Rhino.GetObject("Select centerline curve", 4)
	If IsNull(sCrv) Then Exit Sub
	
	Dim GrpOn:GrpOn = False
	
	If Rhino.ObjectGripsOn(sCrv)  Then 
		Rhino.EnableObjectGrips sCrv, False
		GrpOn = True
	End If
	
	
	Dim angTol: angTol = Rhino.GetReal(" Centerline curve sample tolerance angle in degrees", oldAngTol, 0, 45)
	If isNull(angTol) Then Exit Sub
	OldAngTol = angTol

	Dim SeamCrv: SeamCrv = True		
	Dim sCrv2: sCrv2 = Rhino.GetObject("Select seam curve, Enter for none.", 4)
	If IsNull(sCrv2) Then 
		SeamCrv = False
	End If
	
	Dim CSamp: CSamp = Rhino.GetInteger("Samples around curve", OldCSamp, 4)
	If isNull(Csamp) Then Exit Sub
	OldCSamp = CSamp 'samples around curve
	
	Dim LSamp, temp, stemp, r
	
	If Rhino.IsLine(sCrv) Then
		temp = Rhino.DivideCurve(sCrv, 32, False)
		ReDim LSamp(33)
		For Each stemp In temp
			lSamp(r) = Rhino.CurveClosestPoint(sCrv, temp(r))
			r = r + 1
		Next
	Else
		LSamp = ConvertCurve(sCrv, angtol)
	End If
		
	
	'	Dim LSamp: LSamp = Rhino.GetInteger("Samples along curve",OldLSamp,4)
	'	If isNull(LSamp) Then Exit Sub
	'	OldLSamp = LSamp 'samples along curve

	
	Dim dblAng: dblAng = (360 / (CSamp))
	Dim aBB: aBB = Rhino.BoundingBox(sMesh)
	Dim Dist: Dist = Rhino.Distance(aBB(0), aBB(6))

	'Dim aDiv: aDiv = Rhino.DivideCurve(sCrv,LSamp,False, False)
	
	Dim i, param, plane, aInt, line, n, aPts(), g, aExtra
	Dim testPt1, testPt2,TestVec, testCrv2
	g = 0
	Rhino.EnableRedraw(False)
	

	For i = 0 To uBound(LSamp)
		
		'param =  LSamp(i)
		plane = rhino.CurvePerpFrame(sCrv, LSamp(i))
		'DrawPlaneFrame  Plane, 10'TEST
		
		If SeamCrv = True Then
			testPt1 = Rhino.EvaluateCurve(sCrv, lsamp(i))
			TestPt2 = Rhino.EvaluateCurve(sCrv2, Rhino.CurveClosestPoint(sCrv2, Testpt1))
			TestVec = Rhino.VectorUnitize(Rhino.VectorCreate(TestPt2, Testpt1))
			Plane(1) = testVec
		End If
		
		'	Line = Rhino.AddLine(Plane(0), Rhino.PointAdd(Plane(0), Rhino.VectorScale(plane(1), Dist)))
		Line = array(Plane(0), Rhino.PointAdd(Plane(0), Rhino.VectorScale(plane(1), Dist)))
		
		'	If i = Lsamp Then rhino.EnableRedraw'TEST
		For n = 0 To CSamp - 1
			
			aInt = Rhino.LineMeshIntersection(Line, sMesh)
			If UBound(aInt) > 0 then
				apts(g) = aInt(Rhino.PointArrayClosestPoint(aInt, plane(0)))
			else aPts(g) = aint(0)
			End if

			RotateLine Line, Plane(0), SAng, plane(3), False
			'Rhino.RotateObject Line, Plane(0), SAng, plane(3), False
			g = g + 1
	
		Next
		
		ReDim Preserve aPts(g)

		aPts(g) = aPts(g - n)

		g = g + 1

		'	Rhino.DeleteObject Line

	Next
	
	If isUpperBound(aPts) Then
		
		If Ubound(aPts) = (((uBound(LSamp) + 1) * (CSamp + 1))) - 1 Then
			Dim sSrf: sSrf = MakeTube(aPts, uBound(LSamp) + 1, CSamp + 1)
			
			If Not IsNull(sSrf) Then
				Rhino.UnselectAllObjects
				Rhino.SelectObject sSrf
				Rhino.Command "_MakeUniform"
			End If
			
		End If

	End If
	
	If GrpOn = True Then Rhino.EnableObjectGrips scrv, True
	Rhino.EnableRedraw
End Sub

Sub RotateLine(ByRef Line, aPt, dblAng, VecDir)
	
	vec = Rhino.VectorCreate(line(1), line(0))
	RotateLine = array(aPt, Rhino.PointAdd(apt, Rhino.VectorRotate(vec, dblAng, VecDir)))
	
End Sub

Function MakeTube(aPts, LSamp, CSamp)

	'The array must contain arrPointCount(0) + arrDegree(0) - 1 elements.
	Dim i
	Dim aCount:	aCount = array(LSamp, CSamp)
	
	Dim aKnotsU
	ReDim aKnotsU(LSamp + 1)
	
	For i = 0 To 2
		aKnotsU(i) = 0
	Next
	
	For i = 3 To LSamp - 1
		aKnotsU(i) = aKnotsU(i - 1) + (1 / LSamp)
	Next
	
	For i =  LSamp - 1 To  LSamp + 1
		aKnotsU(i) = 1
	Next
	
	Dim aKnotsV
	ReDim aKnotsV(CSamp + 1)
	
	For i = 0 To 2
		aKnotsV(i) = 0
	Next
	
	For i = 3 To CSamp
		aKnotsV(i) = aKnotsV(i - 1) + (1 / CSamp)
	Next
	
	For i =  CSamp - 1 To  CSamp + 1
		aKnotsV(i) = 1
	Next
		
	Dim aDeg: aDeg = array(3, 3)
	Dim aWts
	ReDim aWts((Lsamp*Csamp)-1)
	
	For i = 0 To ((LSamp * CSamp) - 1)
		aWts(i) = 1
	Next
	
	MakeTube = Rhino.AddNurbsSurface(aCount, aPts, aKnotsU, aKnotsV, aDeg, aWts)
	
End Function

Function ConvertCurve(sCrv, angTol)
	
	Rhino.UnselectAllObjects
	Rhino.SelectObject sCrv
	Rhino.Command "_Convert _Output=_Lines _AngleTolerance=" & CStr (AngTol) & " _DeleteInput=_No _Enter"
	
	If Rhino.LastCommandResult = 0 Then
		
		Dim sPoly: sPoly = Rhino.LastCreatedObjects()(0)
		Dim apts: aPts = Rhino.PolylineVertices(sPoly)
		
	End If
	Dim aresults(),m, i
	m = 0
	
	If isArray(aPts) Then
		For i = 0 To UBound(aPts)
			ReDim Preserve aresults(m)
			aresults(m) = Rhino.CurveClosestPoint(sCrv, apts(i))
				
			m = m + 1
		Next
	End If
	Rhino.DeleteObject sPoly
	ConvertCurve = aResults
	
End Function


Function IsUpperBound(ByRef arr)

	IsUpperBound = False

	If IsArray(arr) Then

		On Error Resume Next

		UBound arr

		If Err.Number = 0 Then IsUpperBound = True

	End If

End Function

Sub DrawPlaneFrame (aPlane, dblScale)'TESTING ONLY
	
	Dim pt0: Pt0 = aPlane(0)
	
	Dim vec1: vec1 = Rhino.VectorScale(aPlane(1), dblScale)
	Dim pt1: Pt1 = Rhino.PointAdd(aPlane(0), vec1)
	

	Dim vec2: vec2 = Rhino.VectorScale(aPlane(2), dblScale)
	Dim pt2: Pt2 = Rhino.PointAdd(aPlane(0), Vec2)	

	Dim vec3: vec3 = Rhino.VectorScale(aPlane(3), dblScale)
	Dim pt3: Pt3 = Rhino.PointAdd(aPlane(0), Vec3)	
	
	Dim Line1: Line1 = Rhino.AddLine(Pt0, Pt1)
	Dim Line2: Line2 = Rhino.AddLine(Pt0, pt2)
	Dim Line3: Line3 = Rhino.AddLine(Pt0, Pt3)
	
	Rhino.ObjectColor line1, vbred
	Rhino.ObjectColor line2, vbgreen
	rhino.ObjectColor line3, vbBlue
	
	Dim sgrp: sGrp = Rhino.AddGroup
	
	Rhino.AddObjectsToGroup array(Line1, Line2, Line3), sGrp
	
End Sub
