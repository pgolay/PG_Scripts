Function IsStringInArray(item, arr, intCase)
	'Non case-sensitive= 0, case-sensitive = 1

	
	IsStringInArray = False
	Dim sItem
		
	If intCase = 0 Then
		For Each sItem In arr
			If LCase(sItem) = LCase(Item) Then
				IsStringInArray = True
				Exit For
			End If
		Next
	Else
		For Each sItem In arr
			If sItem = Item Then
				IsStringInArray = True
				Exit For
			End If
		Next	
	End If
	
End Function
