Function GetUntrimmedSrf(sSrf)
	'returns the untrimmed version of the selected surface
	'for analytical surfaces the entire shape is returned.
	Dim aPlane,dblRad,dblHeight
	
	If Rhino.IsSphere(sSrf) then
		'get sphere info
		'make a new sphere
		
		Dim aSphere: aSphere = Rhino.SurfaceSphere(sSrf)
		aPlane = aSphere(0)
		dblRad = aSphere(1)
		GetUntrimmedSrf = Rhino.AddSphere(aPlane,dblrad)
		
		'ElseIf Rhino.IsPlaneSurface(sSrf) Then
		'get plane info
		'make a new plane
		
	ElseIf Rhino.IsCone(sSrf) Then
		'get cone info
		'make a new cone
		
		Dim aCone: aCone = Rhino.SurfaceCone(sSrf)
		aPlane = aCone(0)
		dblHeight = aCone(1)
		dblrad = aCone(2)
		GetUntrimmedSrf = Rhino.AddCone(aPlane, dblHeight,dblRad, False)
		
	ElseIf Rhino.IsTorus(sSrf) Then
		'get torus info
		'make a new torus
		
		Dim aTorus: aTorus = Rhino.SurfaceTorus(sSrf)
		aPlane = aTorus(0)
		dblrad = atorus(1)
		Dim dblrad1: dblRad1 = aTorus(2)
		GetUntrimmedSrf = Rhino.AddTorus(aPlane, dblRad, dblRad1,aPlane(3))
		
	Else 
		'get surface info
		'make a new surface
		
		Dim aPtCount: aptCount = Rhino.SurfacePointCount(sSrf)
		Dim aPts: aPts = Rhino.SurfacePoints(sSrf)
		
		Dim aKnotCount: aKnotCount = Rhino.SurfaceKnotCount(sSrf)
		Dim aKnots: aKnots = Rhino.SurfaceKnots(sSrf)
		
		Dim aKnotsU: aKnotsU = aKnots(0)
		Dim aKnotsV: aKnotsV =  aKnots(1)
		
		Dim aDegree:aDegree = Rhino.SurfaceDegree(sSrf)
		Dim aWeights:aWeights = Rhino.SurfaceWeights (sSrf)
		
		GetUntrimmedSrf = Rhino.AddNurbsSurface(aPtCount, aPts, aKnotsU, aKnotsV, aDegree, aWeights)

	End If
	
End Function
