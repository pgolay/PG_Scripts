Function GetFileName(sFile)

	Dim intLen,intDot, intSlash, intFile, intStart
	intLen = len(sFile)
	intDot = instrRev(sFile,".")
	intSlash = instrRev(sFile,"\")+1
	intFile = intDot-IntSlash
	intStart = intLen-(intlen-intSlash)


	GetFilename = mid(sFile,intStart,intFile)
End Function

Function GetFileName(Path)
    
	'Get the filename without the path or extension.
	'Input Values:
	'   flname - path and filename of file.
	'Return Value:
	'   GetFileName - name of file without the extension.
    
	Dim posn , i 
	Dim fName
    
	posn = 0
	'find the position of the last "\" character in filename
	For i = 1 To Len(path)
		If (Mid(path, i, 1) = chr(92)) Then posn = i
	Next 

	'get filename without path
	fName = Right(path, Len(path) - posn)

	'get filename without extension
	posn = InStr(fName, ".")
	If posn <> 0 Then
		fName = Left(fName, posn - 1)
	End If
	
	GetFileName = fName
	
End Function
