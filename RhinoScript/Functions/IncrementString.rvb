'\\\\\\\\\\\\\\\\\\\\\\\\\\\\\
'/////////////////////////////
'Increment a string with a 3 digit number

Function IncrementName(strName)
	Dim name, num, last3, last4, length, str
	Dim Zeros, incr	  , X
	X = False
		Last3 = Right(strName, 3)
		Last4= Right(strName, 4)
		Length = Len(Last3)


	'check for spaces in the last 3 characters of the name
	Dim arrLast(2) , i
	arrlast(0)=Left(Last3,1)
		arrlast(1)=Mid(Last3,2,1)
	arrlast(1)=Right(Last3,1)

	For i = 0 To 2
		If arrLast(i)=" " Then
			X = True
			str = strName &"_001"
			If Rhino.isLayer (str) Then
				str =IncrementName(str)
			End If
			Exit for
		End If
	Next


	'  Rhino.Print Last3'Test
	If IsNumeric(Last3) And X = False Then
		If Not IsNumeric(Last4) Then
			Num = (Last3) + 1
			'      Rhino.Print "num = " &num'Test
			Zeros = String(3-Len(Num),"0")
			'      Rhino.Print "Zeros = " &Zeros'Test
			incr = Zeros & Num
			str = Replace(strName,Last3,incr)
			Else
			str = strname &"_001"
		End If
	Else
		str = strName &"_001"
		If Rhino.isLayer (str) Then
			str =IncrementName(str)
		End If
	End If
	IncrementName= str

End Function
'\\\\\\\\\\\\\\\\\\\\\\\\\\\\\
'/////////////////////////////
