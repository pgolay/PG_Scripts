Function IsSinglePt(apts, dblTol)
	IsSinglePt = False
	dim aBB: aBB = Rhino.PointArrayBoundingBox(aPts)
	If QDistance (aBB(0), aBB(6)) < dblTol then IsSinglept = True
	
End Function

Function QDistance(aPtA,aPtB)
	QDistance = Sqr( (aPtA(0 )- aPtB(0))^2 + (aPtA(1)- aPtB(1))^2 + (aPtA(2) - aPtB(2))^2 )
End Function
